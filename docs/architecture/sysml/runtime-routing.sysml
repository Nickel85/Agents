// Generated by `mongoose architecture generate`. Do not edit by hand.
package MongooseRuntimeRouting {
  action def InstallAgent;
  action def ValidateManifest;
  action def DiscoverCapabilities;
  action def RouteRequest;
  action def DispatchCapability;
  action def ReadExternalApi;
  action runtimeRequestFlow {
    first start;
    then validateManifest : ValidateManifest;
    then discoverCapabilities : DiscoverCapabilities;
    then routeRequest : RouteRequest;

    then Njord_brief : DispatchCapability;
    // branch taskTypes: brief, finance, financial-brief, weekly-brief, ynab
    then Njord_brief_ReadYNAB : ReadExternalApi;
    then Njord_config_status : DispatchCapability;
    // branch taskTypes: configuration, credential-status, setup
    then Njord_finance_review : DispatchCapability;
    // branch taskTypes: cash-flow-forecast, finance, finance-review, financial-risk, review, ynab
    then Njord_finance_review_ReadYNAB : ReadExternalApi;
    then Njord_hello_world : DispatchCapability;
    // branch taskTypes: connection-test, diagnostic
    then Njord_ynab_budget_summary : DispatchCapability;
    // branch taskTypes: budget-summary, finance, review-needed, ynab
    then Njord_ynab_budget_summary_ReadYNAB : ReadExternalApi;
    then Njord_ynab_spending_review : DispatchCapability;
    // branch taskTypes: cash-flow, finance, spending-review, transactions, ynab
    then Njord_ynab_spending_review_ReadYNAB : ReadExternalApi;

    then Portfolio_thesis : DispatchCapability;
    // branch taskTypes: investment-thesis, memory, portfolio, research-review, thesis

    then done;
  }
}
